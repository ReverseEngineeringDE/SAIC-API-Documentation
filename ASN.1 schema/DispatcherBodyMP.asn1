--
-- 
-- Message format for Dispatcher Body of the OTA protocol data
--
-- * Copyright (c) 2012 SAIC. All Rights Reserved.
--
-- 2012-04-28 v1.0 First released version.
--
--

OTA_DispatcherBodyMP

DEFINITIONS
AUTOMATIC TAGS ::= 
BEGIN

--
-- Dispatcher Body (MP)
--
DispatcherBodyMP ::= SEQUENCE
{
-- User ID, uniqe  identifier of user
   uid IA5String(SIZE(50)) OPTIONAL,

-- Token of conversation
   token IA5String(SIZE(32)) OPTIONAL,

-- uniqe identifier of Application
    applicationID  IA5String(SIZE(3)),

-- VIN,17 ASCII characters 
    vin  IA5String(SIZE(17)) OPTIONAL,

-- Event Creation Time,use the seconds from 1970-01-01 00:00:00   
    eventCreationTime  INTEGER(0..4294967295),

-- Event ID    
    eventID  INTEGER(0..281474976710655) OPTIONAL,

-- Message ID,uniqe identifier of message    
    messageID  INTEGER(0..255),

-- Message Counter   
    messageCounter MessageCounter,

-- ACK Required,the flag of if the acknowledge signal is required     
    ackRequired  BOOLEAN OPTIONAL,

-- Stateless Dispatcher Message ,true:Stateless,false:not Stateless
    statelessDispatcherMessage BOOLEAN OPTIONAL,

-- Calling Request Message    
    crqmRequest  BOOLEAN OPTIONAL,

-- Basic Position  
    basicPosition BasicPosition OPTIONAL,

-- Network Info   
    networkInfo NetworkInfo OPTIONAL,

-- SIM Info    
    simInfo  NumericString(SIZE(19)) OPTIONAL,

-- HMI Language ,0:Simplified Chinese;1:English   
    hmiLanguage LanguageType OPTIONAL,

-- ICC ID, uniqe identifier of SIM card   
    iccID  NumericString(SIZE(20)),

-- Application Data Message Length    
    applicationDataLength  INTEGER(0..4294967295),

-- Application Data Encoding,0:ASN.1 PER unaligned;1:ASN.1 DER;2:ASN.1 BER    
    applicationDataEncoding DataEncodingType,

-- Application Data Protocol Version   
    applicationDataProtocolVersion  INTEGER(0..65535),

-- Test Flag 01:test;10:prd;11:both    
    testFlag  INTEGER(1..3) OPTIONAL,

-- Result from TAP server
    result  INTEGER(0..65535) OPTIONAL,

-- Error Message
    errorMessage  OCTET STRING(SIZE(1..128)) OPTIONAL
}

--
-- Message Counter
--
MessageCounter ::= SEQUENCE
{
--  Uplink Counter
    uplinkCounter INTEGER(0..255),

-- Downlink Counter
    downlinkCounter INTEGER(0..255)
}

--
-- Basic Position
--
BasicPosition ::= SEQUENCE
{
  
  --WGS84 decimal X 1000000 e.g. latitude 57.123456 => 57123456 
  latitude  INTEGER (-90000000..90000000),

  --WGS84 decimal X 1000000 e.g. longitude 10.123456 => 10123456
  longitude INTEGER (-180000000..180000000)
}

--
-- Network Info
--
NetworkInfo ::= SEQUENCE
{
-- Mobile Country Code for current network
    mccNetwork  NumericString(SIZE(3)),

-- Mobile Network Code for current network
    mncNetwork NumericString(SIZE(3)),

-- Mobile Country Code for the SIM card
    mccSim NumericString(SIZE(3)),

-- Mobile Network Code for the SIM card
    mncSim NumericString(SIZE(3)),

-- Signal Strength
    signalStrength  INTEGER(0..99)
}

--
-- Language Type
--
LanguageType ::= ENUMERATED
{
-- 0:Simplified Chinese 
  simplifiedChinese(0),

-- 1:English
        english(1)
}

--
-- Data Encoding Type
--
DataEncodingType ::= ENUMERATED
{
-- 0:ASN.1 PER unaligned
        perUnaligned(0),
-- 1:ASN.1 DER
        der(1),
-- 2:ASN.1 BER
        ber(2)
    }

END
